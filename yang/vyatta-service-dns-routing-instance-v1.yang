module vyatta-service-dns-routing-instance-v1 {
	namespace "urn:vyatta.com:mgmt:vyatta-service-dns-routing-instance:1";
	prefix vyatta-service-dns-routing-instance-v1;

	import configd-v1 {
		prefix configd;
	}
	import vyatta-system-network-routing-instance-v1 {
		prefix rt-sys-net;
	}
	import vyatta-routing-v1 {
		prefix rt-instance;
	}
	import vyatta-service-dns-v1 {
		prefix service-dns;
	}

	organization "AT&T Inc.";
	contact
		"AT&T
		 Postal: 208 S. Akard Street
				 Dallas, TX 75202
		 Web: www.att.com";

	description
		"Copyright (c) 2018-2019, AT&T Intellectual Property.
		All rights reserved.

		Copyright (c) 2014-2017 by Brocade Communications Systems, Inc.
		All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		 The YANG module for vyatta-service-dns-routing-instance-v1";

	revision 2018-07-26 {
		description "RPCs for VCI conversion";
	}

	revision 2016-04-18 {
		description "Add dns to routing instance.";
	}

	augment /rt-instance:routing/rt-instance:routing-instance/rt-instance:service {
		container dns {
			presence "Enable service DNS for routing instance";
			description "Dns service in routing-instance";
			configd:help "Domain Name Server (DNS) parameters";
			uses service-dns:dns-service-forwarding {
				refine forwarding/system {
					must "/rt-instance:routing/rt-instance:routing-instance/rt-instance:system/rt-sys-net:name-server" {
					error-message
						"No name-servers set under 'routing-instance system name-server";
					}
				}
			}
			uses service-dns:dns-service-dynamic;
		}
	}
	augment /service-dns:reset-dns-forwarding/service-dns:input {
		leaf routing-instance {
			type string;
		}
	}
	augment /service-dns:reset-dns-forwarding-cache/service-dns:input {
		leaf routing-instance {
			type string;
		}
	}
}
