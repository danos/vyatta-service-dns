module vyatta-op-service-dns-routing-instance-v1 {
	namespace "urn:vyatta.com:mgmt:vyatta-op-service-dns-routing-instance:1";
	prefix "vyatta-op-service-dns-routing-instance-v1";

	import vyatta-opd-extensions-v1 {
		prefix opd;
	}
	import vyatta-op-reset-v1 {
		prefix reset;
	}
	import vyatta-op-show-v1 {
		prefix show;
	}
	import vyatta-op-update-v1 {
		prefix update;
	}
	import vyatta-op-service-dns-v1 {
		prefix dns;
	}

	organization "AT&T Inc.";
	contact
		"AT&T
		 Postal: 208 S. Akard Street
				 Dallas, TX 75202
		 Web: www.att.com";
	
	description
		"Copyright (c) 2018-2019, AT&T Intellectual Property.
		All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		YANG module for DNS-related operation mode commands.";

	revision 2018-08-03 {
		description "Conversion from node files";
	}
	opd:augment /reset:reset/dns:dns/dns:forwarding/dns:all {
		opd:option routing-instance {
			opd:help "Routing-instance to reset DNS forwarding " +
				"cache and counters";
			opd:on-enter "/lib/vci-service-dns/dns-forwarding-op "+
				"--action=\"reset-all\" "+
				"--vrf=\"$6\"";
			type string;
		}
	}
	opd:augment /reset:reset/dns:dns/dns:forwarding/dns:cache {
		opd:option routing-instance {
			opd:help "Routing-instance to reset DNS forwarding cache";
			opd:on-enter "/lib/vci-service-dns/dns-forwarding-op "+
				"--action=\"reset-cache\" "+
				"--vrf=\"$6\"";
			type string;
		}
	}
	opd:augment /show:show/dns:dns/dns:forwarding/dns:nameservers {
		opd:option routing-instance {
			opd:help "Routing-instance to show DNS forwarding nameservers";
			opd:on-enter "/lib/vci-service-dns/dns-forwarding-op "+
				"--action=\"show-ns\" "+
				"--vrf=\"$6\"";
			type string;
		}
	}
	opd:augment /show:show/dns:dns/dns:forwarding/dns:statistics {
		opd:option routing-instance {
			opd:help "Routing-instance to show DNS forwarding stats";
			opd:on-enter "/lib/vci-service-dns/dns-forwarding-op "+
				"--action=\"show-stats\" "+
				"--vrf=\"$6\"";
			type string;
		}
	}
	opd:augment /show:show/dns:dns/dns:dynamic/dns:status {
		opd:option routing-instance {
			opd:help "Routing-instance to show dynamic DNS status";
			opd:on-enter "/lib/vci-service-dns/dns-dynamic-op " +
				"--action=show -- " +
				"--vrf $6";
			type string;
		}
	}
}
