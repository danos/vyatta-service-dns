module vyatta-op-service-dns-v1 {
	namespace "urn:vyatta.com:mgmt:vyatta-op-service-dns:1";
	prefix "vyatta-op-service-dns-v1";

	import vyatta-opd-extensions-v1 {
		prefix opd;
	}
	import vyatta-op-monitor-v1 {
		prefix monitor;
	}
	import vyatta-op-reset-v1 {
		prefix reset;
	}
	import vyatta-op-show-v1 {
		prefix show;
	}
	import vyatta-op-show-log-v1 {
		prefix show-log;
	}
	import vyatta-op-update-v1 {
		prefix update;
	}

	organization "AT&T Inc.";
	contact
		"AT&T
		 Postal: 208 S. Akard Street
				 Dallas, TX 75202
		 Web: www.att.com";
	
	description
		"Copyright (c) 2018-2019, AT&T Intellectual Property.
		All rights reserved.

		Redistribution and use in source and binary forms, with or without
		modification, are permitted provided that the following conditions
		are met:

		  1. Redistributions of source code must retain the above copyright
		     notice, this list of conditions and the following disclaimer.
		  2. Redistributions in binary form must reproduce the above
		     copyright notice, this list of conditions and the following
		     disclaimer in the documentation and/or other materials provided
		     with the distribution.
		  3. Neither the name of the copyright holder nor the names of its
		     contributors may be used to endorse or promote products derived
		     from this software without specific prior written permission.

		THIS SOFTWARE IS PROVIDED BY THE COPYRIGHT HOLDERS AND CONTRIBUTORS
		'AS IS' AND ANY EXPRESS OR IMPLIED WARRANTIES, INCLUDING, BUT NOT
		LIMITED TO, THE IMPLIED WARRANTIES OF MERCHANTABILITY AND FITNESS
		FOR A PARTICULAR PURPOSE ARE DISCLAIMED. IN NO EVENT SHALL THE
		COPYRIGHT HOLDER OR CONTRIBUTORS BE LIABLE FOR ANY DIRECT, INDIRECT,
		INCIDENTAL, SPECIAL, EXEMPLARY, OR CONSEQUENTIAL DAMAGES (INCLUDING,
		BUT NOT LIMITED TO, PROCUREMENT OF SUBSTITUTE GOODS OR SERVICES;
		LOSS OF USE, DATA, OR PROFITS; OR BUSINESS INTERRUPTION) HOWEVER
		CAUSED AND ON ANY THEORY OF LIABILITY, WHETHER IN CONTRACT, STRICT
		LIABILITY, OR TORT (INCLUDING NEGLIGENCE OR OTHERWISE) ARISING IN
		ANY WAY OUT OF THE USE OF THIS SOFTWARE, EVEN IF ADVISED OF THE
		POSSIBILITY OF SUCH DAMAGE.

		SPDX-License-Identifier: BSD-3-Clause

		 YANG module for DNS-related operation mode commands.";

	revision 2018-08-03 {
		description "Conversion from node files";
	}
	opd:augment /monitor:monitor {
		opd:command dns {
			opd:help "Monitor a Domain Name Service (DNS) daemon";
			opd:command forwarding {
				opd:help "Monitor DNS forwarding";
				opd:on-enter "vyatta-monitor  DNS-Forward dnsmasq";
			}
			opd:command dynamic {
				opd:help "Monitor Dynamic DNS";
				opd:on-enter "vyatta-monitor  Dynamic-DNS ddclient";
			}
		}
	}
	opd:augment /reset:reset {
		opd:command dns {
			opd:help "Reset Domain Name Server (DNS) variables";
			opd:command forwarding {
				opd:help "Reset DNS forwarding variables";
				opd:command all {
					opd:help "Reset DNS forwarding cache and counters";
					opd:on-enter "/lib/vci-service-dns/dns-forwarding-op " +
						"--action=\"reset-all\"";
				}
				opd:command cache {
					opd:help "Reset DNS forwarding cache";
					opd:on-enter "/lib/vci-service-dns/dns-forwarding-op " +
						"--action=\"reset-cache\"";
				}
			}
		}
	}
	opd:augment /show:show {
		opd:command dns {
			opd:help "Show Domain Name Server (DNS) information";
			opd:command forwarding {
				opd:help "Show DNS forwarding information";
				opd:command nameservers {
					opd:help "Show DNS forwarding nameservers information";
					opd:on-enter "/lib/vci-service-dns/dns-forwarding-op " +
						"--action=\"show-ns\"";
				}
				opd:command statistics {
					opd:help "Show DNS forwarding statistics";
					opd:on-enter "/lib/vci-service-dns/dns-forwarding-op " +
						"--action=\"show-stats\"";
				}
			}
			opd:command dynamic {
				opd:help "Show Dynamic DNS information";
				opd:command status {
					opd:help "Show Dynamic DNS status";
					opd:on-enter "/lib/vci-service-dns/dns-dynamic-op " +
						"--action=show";
				}
			}
		}
	}
	opd:augment /show:show/show-log:log {
		opd:command dns {
			opd:help "Show log for Domain Name Service (DNS)";
			opd:command forwarding {
				opd:help "Show log for DNS Forwarding";
				opd:on-enter "journalctl -a --no-pager | grep -e \"dnsmasq\"";
			}
			opd:command dynamic {
				opd:help "Show log for Dynamic DNS";
				opd:on-enter "journalctl -a --no-pager | grep -e \"ddclient\"";
			}
		}
	}
	opd:augment /update:update {
		opd:command dns {
			opd:help "Update DNS information";
			opd:command dynamic {
				opd:help "Update Dynamic DNS information";
				opd:option interface {
					opd:help "Update Dynamic DNS for specified interface";
					opd:allowed "/lib/vci-service-dns/dns-dynamic-op " +
						"--action=list-interfaces";
					opd:on-enter "/lib/vci-service-dns/dns-dynamic-op " +
						"--action=update-interface -- " +
						"--dev=$5";
					type string;
				}
			}
		}
	}
}
